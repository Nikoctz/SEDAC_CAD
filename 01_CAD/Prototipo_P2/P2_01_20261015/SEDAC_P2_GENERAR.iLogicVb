' SEDAC P2.01 - Maqueta geometrica, cotas provisionales.
' Cada ejecucion genera una carpeta nueva. No cambia fuentes P0.
' Bocetos editables sin acotacion completa. Ensamblaje Grounded.
' Cambiar cotas de las llamadas Block y regenerar; no es asociativo.
Sub Main()
 Dim root As String = "C:\Users\nicol\OneDrive\Documentos\SEDAC_CAD\01_CAD\Prototipo_P2\P2_01_20261015"
 Dim output As String = System.IO.Path.Combine(root,"Inventor_" & DateTime.Now.ToString("yyyyMMdd_HHmmss") & "_" & Guid.NewGuid().ToString("N").Substring(0,6))
 System.IO.Directory.CreateDirectory(output)
 Dim stage As String = "Inicio"
 Try
  Dim paths As New System.Collections.Generic.List(Of String)
  Dim p As Inventor.PartDocument = Nothing

  stage = "Riel_I"
  p = NewPart()
  Block(p,"Vol_1",-105,0,0,30,420,1.5,False)
  Block(p,"Vol_2",-105,0,1.5,1.5,420,13.5,False)
  Block(p,"Vol_3",-76.5,0,1.5,1.5,420,13.5,False)
  Finish(p,System.IO.Path.Combine(output,"Riel_I.ipt"),163,184,200)
  paths.Add(System.IO.Path.Combine(output,"Riel_I.ipt"))
  p.Close(True)
  stage = "Riel_D"
  p = NewPart()
  Block(p,"Vol_1",75,0,0,30,420,1.5,False)
  Block(p,"Vol_2",75,0,1.5,1.5,420,13.5,False)
  Block(p,"Vol_3",103.5,0,1.5,1.5,420,13.5,False)
  Finish(p,System.IO.Path.Combine(output,"Riel_D.ipt"),163,184,200)
  paths.Add(System.IO.Path.Combine(output,"Riel_D.ipt"))
  p.Close(True)
  stage = "Travesano_1"
  p = NewPart()
  Block(p,"Vol_1",-105,50,-2,210,30,2,False)
  Finish(p,System.IO.Path.Combine(output,"Travesano_1.ipt"),111,140,158)
  paths.Add(System.IO.Path.Combine(output,"Travesano_1.ipt"))
  p.Close(True)
  stage = "Travesano_2"
  p = NewPart()
  Block(p,"Vol_1",-105,210,-2,210,30,2,False)
  Finish(p,System.IO.Path.Combine(output,"Travesano_2.ipt"),111,140,158)
  paths.Add(System.IO.Path.Combine(output,"Travesano_2.ipt"))
  p.Close(True)
  stage = "Travesano_3"
  p = NewPart()
  Block(p,"Vol_1",-105,360,-2,210,30,2,False)
  Finish(p,System.IO.Path.Combine(output,"Travesano_3.ipt"),111,140,158)
  paths.Add(System.IO.Path.Combine(output,"Travesano_3.ipt"))
  p.Close(True)
  stage = "Cuna"
  p = NewPart()
  Block(p,"Vol_1",-140,0,1.5,280,2,140,False)
  Block(p,"Vol_2",-140,2,1.5,280,58,2,False)
  Block(p,"Vol_3",-140,2,3.5,2,15,138,False)
  Block(p,"Vol_4",138,2,3.5,2,15,138,False)
  Block(p,"Abertura_1",-30,-0.1,81.5,60,2.2,61,True)
  Finish(p,System.IO.Path.Combine(output,"Cuna.ipt"),163,184,200)
  paths.Add(System.IO.Path.Combine(output,"Cuna.ipt"))
  p.Close(True)
  stage = "Anclaje_I"
  p = NewPart()
  Block(p,"Vol_1",-125,320,15,70,60,3,False)
  Block(p,"Abertura_1",-116,365,14.9,52,5,3.2,True)
  Block(p,"Abertura_2",-105.1,330,14.9,6.2,20,3.2,True)
  Block(p,"Abertura_3",-81.1,330,14.9,6.2,20,3.2,True)
  Finish(p,System.IO.Path.Combine(output,"Anclaje_I.ipt"),236,151,63)
  paths.Add(System.IO.Path.Combine(output,"Anclaje_I.ipt"))
  p.Close(True)
  stage = "Anclaje_D"
  p = NewPart()
  Block(p,"Vol_1",55,320,15,70,60,3,False)
  Block(p,"Abertura_1",64,365,14.9,52,5,3.2,True)
  Block(p,"Abertura_2",74.9,330,14.9,6.2,20,3.2,True)
  Block(p,"Abertura_3",98.9,330,14.9,6.2,20,3.2,True)
  Finish(p,System.IO.Path.Combine(output,"Anclaje_D.ipt"),236,151,63)
  paths.Add(System.IO.Path.Combine(output,"Anclaje_D.ipt"))
  p.Close(True)
  stage = "REF_Interfaz_HDPE"
  p = NewPart()
  Block(p,"Vol_1",-130,15,-4.5,260,390,2.5,False)
  Finish(p,System.IO.Path.Combine(output,"REF_Interfaz_HDPE.ipt"),47,106,115)
  paths.Add(System.IO.Path.Combine(output,"REF_Interfaz_HDPE.ipt"))
  p.Close(True)
  stage = "REF_Pad_I"
  p = NewPart()
  Block(p,"Vol_1",-110,90,-14.5,90,240,10,False)
  Finish(p,System.IO.Path.Combine(output,"REF_Pad_I.ipt"),49,62,75)
  paths.Add(System.IO.Path.Combine(output,"REF_Pad_I.ipt"))
  p.Close(True)
  stage = "REF_Pad_D"
  p = NewPart()
  Block(p,"Vol_1",20,90,-14.5,90,240,10,False)
  Finish(p,System.IO.Path.Combine(output,"REF_Pad_D.ipt"),49,62,75)
  paths.Add(System.IO.Path.Combine(output,"REF_Pad_D.ipt"))
  p.Close(True)
  stage = "REF_Pad_Lumbar"
  p = NewPart()
  Block(p,"Vol_1",-100,20,-14.5,200,50,10,False)
  Finish(p,System.IO.Path.Combine(output,"REF_Pad_Lumbar.ipt"),49,62,75)
  paths.Add(System.IO.Path.Combine(output,"REF_Pad_Lumbar.ipt"))
  p.Close(True)

  stage = "Ensamblaje"
  Dim assy As Inventor.AssemblyDocument = CType(ThisApplication.Documents.Add(Inventor.DocumentTypeEnum.kAssemblyDocumentObject,ThisApplication.FileManager.GetTemplateFile(Inventor.DocumentTypeEnum.kAssemblyDocumentObject),True),Inventor.AssemblyDocument)
  assy.UnitsOfMeasure.LengthUnits = Inventor.UnitsTypeEnum.kMillimeterLengthUnits
  For Each path As String In paths
   Dim occ As Inventor.ComponentOccurrence = assy.ComponentDefinition.Occurrences.Add(path,ThisApplication.TransientGeometry.CreateMatrix())
   occ.Name = System.IO.Path.GetFileNameWithoutExtension(path)
   occ.Grounded = True
  Next
  If Not assy.Update2(False) Then Throw New Exception("Fallo al actualizar ensamblaje")
  If assy.ComponentDefinition.Occurrences.Count <> 12 Then Throw New Exception("Se esperaban 12 piezas")
  assy.SaveAs(System.IO.Path.Combine(output,"SEDAC_P2_01.iam"),False)
  stage = "Maqueta reducida"
  p = NewPart()

  Block(p,"M_Travesano_1_1",-8.75,4.16666666667,-0.166666666667,17.5,2.5,1.2,False)
  Block(p,"M_Riel_I_1",-8.75,0,0,2.5,35,1.2,False)
  Block(p,"M_Riel_I_2",-8.75,0,0.125,1.2,35,1.2,False)
  Block(p,"M_Riel_I_3",-6.375,0,0.125,1.2,35,1.2,False)
  Block(p,"M_Riel_D_1",6.25,0,0,2.5,35,1.2,False)
  Block(p,"M_Riel_D_2",6.25,0,0.125,1.2,35,1.2,False)
  Block(p,"M_Riel_D_3",8.625,0,0.125,1.2,35,1.2,False)
  Block(p,"M_Travesano_2_1",-8.75,17.5,-0.166666666667,17.5,2.5,1.2,False)
  Block(p,"M_Travesano_3_1",-8.75,30,-0.166666666667,17.5,2.5,1.2,False)
  Block(p,"M_Cuna_1",-11.6666666667,0,0.125,23.3333333333,1.4,11.6666666667,False)
  Block(p,"M_Cuna_2",-11.6666666667,0.166666666667,0.125,23.3333333333,4.83333333333,1.2,False)
  Block(p,"M_Cuna_3",-11.6666666667,0.166666666667,0.291666666667,1.2,1.25,11.5,False)
  Block(p,"M_Cuna_4",11.5,0.166666666667,0.291666666667,1.2,1.25,11.5,False)
  Block(p,"M_Corte_Cuna_1",-2.5,-0.1,6.79166666667,5,1.6,6,True)
  Block(p,"M_Anclaje_I_1",-10.4166666667,26.6666666667,1.25,5.83333333333,5,1.2,False)
  Block(p,"M_Anclaje_D_1",4.58333333333,26.6666666667,1.25,5.83333333333,5,1.2,False)

  Finish(p,System.IO.Path.Combine(output,"SEDAC_P2_Maqueta_1a12_ADAPTADA.ipt"),163,184,200)
  Dim box As Inventor.Box = p.ComponentDefinition.SurfaceBodies.Item(1).RangeBox
  Dim dims As String = ((box.MaxPoint.X-box.MinPoint.X)*10).ToString() & " x " & ((box.MaxPoint.Y-box.MinPoint.Y)*10).ToString() & " x " & ((box.MaxPoint.Z-box.MinPoint.Z)*10).ToString()
  If (box.MaxPoint.X-box.MinPoint.X)*10>40.001 OrElse (box.MaxPoint.Y-box.MinPoint.Y)*10>40.001 OrElse (box.MaxPoint.Z-box.MinPoint.Z)*10>70.001 Then Throw New Exception("Maqueta fuera de limite")
  p.Close(True)
  assy.Activate()
  Dim cam As Inventor.Camera = ThisApplication.ActiveView.Camera
  cam.ViewOrientationType = Inventor.ViewOrientationTypeEnum.kIsoTopRightViewOrientation
  cam.Fit()
  cam.Apply()
  Try
   ThisApplication.ActiveView.SaveAsBitmap(System.IO.Path.Combine(output,"CAPTURA_INVENTOR_P2.png"),1600,1200)
  Catch
  End Try
  System.IO.File.WriteAllText(System.IO.Path.Combine(output,"ESTADO_OK.txt"),"P2.01 generado y actualizado en Inventor. 12 piezas fijadas y maqueta de un cuerpo." & vbCrLf & "Maqueta mm: " & dims & vbCrLf & "Sin validacion estructural ni medidas reales de bomba.")
  System.IO.File.WriteAllText(System.IO.Path.Combine(root,"ULTIMA_EJECUCION.txt"),output)
 Catch ex As Exception
  System.IO.File.WriteAllText(System.IO.Path.Combine(output,"ERROR.txt"),stage & vbCrLf & ex.ToString())
  Throw
 End Try
End Sub
Function NewPart() As Inventor.PartDocument
 Dim p As Inventor.PartDocument = CType(ThisApplication.Documents.Add(Inventor.DocumentTypeEnum.kPartDocumentObject,ThisApplication.FileManager.GetTemplateFile(Inventor.DocumentTypeEnum.kPartDocumentObject),False),Inventor.PartDocument)
 p.UnitsOfMeasure.LengthUnits = Inventor.UnitsTypeEnum.kMillimeterLengthUnits
 Return p
End Function
Sub Block(p As Inventor.PartDocument,label As String,x As Double,y As Double,z As Double,w As Double,h As Double,d As Double,cut As Boolean)
 Dim cd As Inventor.PartComponentDefinition = p.ComponentDefinition
 Dim tg As Inventor.TransientGeometry = ThisApplication.TransientGeometry
 Dim plane As Inventor.WorkPlane = cd.WorkPlanes.Item(3)
 If Math.Abs(z) > 0.00000001 Then
  plane = cd.WorkPlanes.AddByPlaneAndOffset(plane,z/10)
  plane.Visible = False
 End If
 Dim sk As Inventor.PlanarSketch = cd.Sketches.Add(plane)
 sk.Name = "B_" & label
 sk.SketchLines.AddAsTwoPointRectangle(tg.CreatePoint2d(x/10,y/10),tg.CreatePoint2d((x+w)/10,(y+h)/10))
 Dim op As Inventor.PartFeatureOperationEnum = Inventor.PartFeatureOperationEnum.kJoinOperation
 If cut Then op = Inventor.PartFeatureOperationEnum.kCutOperation
 Dim ed As Inventor.ExtrudeDefinition = cd.Features.ExtrudeFeatures.CreateExtrudeDefinition(sk.Profiles.AddForSolid(),op)
 ed.SetDistanceExtent(d/10,Inventor.PartFeatureExtentDirectionEnum.kPositiveExtentDirection)
 cd.Features.ExtrudeFeatures.Add(ed).Name = label
 sk.Visible = False
End Sub
Sub Finish(p As Inventor.PartDocument,path As String,r As Integer,g As Integer,b As Integer)
 If Not p.Update2(False) Then Throw New Exception("Fallo al actualizar " & path)
 If p.ComponentDefinition.SurfaceBodies.Count <> 1 Then Throw New Exception("Pieza no tiene un cuerpo: " & path)
 If Not p.ComponentDefinition.SurfaceBodies.Item(1).IsSolid Then Throw New Exception("Pieza no solida")
 p.PropertySets.Item("Inventor User Defined Properties").Add("P2.01 - COTAS PROVISIONALES","SEDAC_Estado")
 Try
  Dim appearance As Inventor.Asset = p.Assets.Add(Inventor.AssetTypeEnum.kAssetTypeAppearance,"Generic","SEDAC_Color","SEDAC_Color")
  CType(appearance.Item("generic_diffuse"),Inventor.ColorAssetValue).Value = ThisApplication.TransientObjects.CreateColor(r,g,b)
  p.ActiveAppearance = appearance
 Catch
 End Try
 p.SaveAs(path,False)
End Sub
