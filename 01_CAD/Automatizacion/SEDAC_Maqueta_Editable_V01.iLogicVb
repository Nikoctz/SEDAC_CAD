' MAQUETA NATIVA EDITABLE. Ejecutar una vez en una pieza Standard.ipt VACIA.
' No lee ni sobrescribe archivos. Guardar manualmente al finalizar.
' Cotas en mm; conversion a cm solo en las llamadas a la API de Inventor.
' Escala de disposicion 1:12, espesores adaptados. Un cuerpo, sin roscas.
' Bocetos editables sin acotacion completa. No es un ensamblaje desmontable.
Sub Main()
    Dim doc As Inventor.PartDocument = TryCast(ThisApplication.ActiveDocument, Inventor.PartDocument)
    If doc Is Nothing Then
        MessageBox.Show("Abre una NUEVA pieza Standard.ipt vacia.", "SEDAC")
        Return
    End If
    Dim cd As Inventor.PartComponentDefinition = doc.ComponentDefinition
    If cd.Features.Count > 0 OrElse cd.Sketches.Count > 0 OrElse cd.SurfaceBodies.Count > 0 Then
        MessageBox.Show("Esta regla requiere una pieza nueva VACIA. No usar el STL ni el kit existente.", "SEDAC")
        Return
    End If
    Dim stage As String = "iniciar"
    Dim tx As Inventor.Transaction = Nothing
    Try
        tx = ThisApplication.TransactionManager.StartTransaction(doc, "SEDAC maqueta editable")
        doc.UnitsOfMeasure.LengthUnits = Inventor.UnitsTypeEnum.kMillimeterLengthUnits
        stage = "panel"
        Block(cd, "M_Panel", 0,0,0,30,35,1.6)
        Dim left As Double = 40.0/12
        Dim front As Double = 1.6+140.0/12
        stage = "piso de cuna"
        Block(cd,"M_Cuna_Piso",left,40.0/12,1.5,280.0/12,1.4,front-1.5)
        stage = "abertura U de cuna"
        ' Dos cortes sobre XZ; el rectangulo solapa la mitad del circulo.
        Dim sk As Inventor.PlanarSketch = cd.Sketches.Add(cd.WorkPlanes.Item(2))
        sk.Name = "B_U_Rectangulo"
        Dim tg As Inventor.TransientGeometry = ThisApplication.TransientGeometry
        sk.SketchLines.AddAsTwoPointRectangle( _
            sk.ModelToSketchSpace(tg.CreatePoint(1.25,0,(front-5)/10)), _
            sk.ModelToSketchSpace(tg.CreatePoint(1.75,0,(front+.2)/10)))
        ExtrudeY(cd,sk,5,"M_U_Rectangulo")
        sk = cd.Sketches.Add(cd.WorkPlanes.Item(2))
        sk.Name = "B_U_Redondo"
        sk.SketchCircles.AddByCenterRadius(sk.ModelToSketchSpace(tg.CreatePoint(1.5,0,(front-5)/10)),.25)
        ExtrudeY(cd,sk,5,"M_U_Redondo")
        stage = "pared y labios de cuna"
        Block(cd,"M_Cuna_Posterior",left,40.0/12,1.5,280.0/12,5.5,1.3)
        Block(cd,"M_Cuna_Labio_I",left,40.0/12+1.3,1.5,1.2,1.2,front-1.5)
        Block(cd,"M_Cuna_Labio_D",left+280.0/12-1.2,40.0/12+1.3,1.5,1.2,1.2,front-1.5)
        Dim axes As New System.Collections.Generic.List(Of Double())
        Dim ai As Integer = 0
        For Each ax As Double In New Double(){50.0/12,220.0/12}
            ai += 1
            Dim label As String = "M_A" & ai.ToString()
            Dim ay As Double = 295.0/12
            stage = "separadores de anclaje " & ai.ToString()
            Dim n As Integer = 0
            For Each x As Double In New Double(){ax+1,ax+6.5}
                n += 1
                Disk(cd,label & "_Separador" & n,x,320.0/12,1.5,1.1,1.4,False)
            Next
            stage = "placa de anclaje " & ai.ToString()
            Block(cd,label & "_Placa",ax-.5,ay-.5,2.8,8.5,7.25,1.4)
            CapsuleCut(cd,label & "_Correa",ax+45.0/12,ay+57.5/12,2.8,52.0/12,1.2,1.4,False)
            n=0
            For Each x As Double In New Double(){ax+1,ax+6.5}
                n+=1
                stage = "ranura y fijacion " & ai.ToString() & "-" & n.ToString()
                CapsuleCut(cd,label & "_Ranura" & n,x,320.0/12,2.8,2.5,1,1.4,True)
                ' Restituye la corona del separador tras cortar la placa.
                Disk(cd,label & "_Corona" & n,x,320.0/12,2.7,1.1,.2,False)
                Disk(cd,label & "_Vastago" & n,x,320.0/12,2.75,.6,2,False)
                axes.Add(New Double(){x,320.0/12,4.2})
            Next
        Next
        For Each x As Double In New Double(){90.0/12,270.0/12}
            For Each y As Double In New Double(){70.0/12,90.0/12}
                axes.Add(New Double(){x,y,2.8})
            Next
        Next
        Dim index As Integer = 0
        For Each a As Double() In axes
            index+=1
            stage = "detalle de fijacion " & index.ToString()
            Dim tag As String = "M_F" & index.ToString()
            Disk(cd,tag & "_Arandela",a(0),a(1),a(2)-.1,1.3,.6,False)
            sk=SketchXY(cd,a(2)+.4,tag & "_Cabeza")
            Hex(sk,a(0),a(1),1.6)
            ExtrudeZ(cd,sk,.8,False,tag & "_Cabeza")
            sk=SketchXY(cd,0,tag & "_ArandelaPosterior")
            sk.SketchCircles.AddByCenterRadius(tg.CreatePoint2d(a(0)/10,a(1)/10),.125)
            sk.SketchCircles.AddByCenterRadius(tg.CreatePoint2d(a(0)/10,a(1)/10),.095)
            ExtrudeZ(cd,sk,.25,True,tag & "_ArandelaPosterior")
            sk=SketchXY(cd,0,tag & "_TuercaPosterior")
            Hex(sk,a(0),a(1),1.45)
            Hex(sk,a(0),a(1),.95)
            ExtrudeZ(cd,sk,.25,True,tag & "_TuercaPosterior")
        Next
        stage="actualizar geometria"
        If Not doc.Update2(False) Then Throw New Exception("Inventor no pudo actualizar la pieza.")
        If cd.SurfaceBodies.Count<>1 Then Throw New Exception("Se esperaba un solo cuerpo integrado.")
        Dim bounds As Inventor.Box=cd.SurfaceBodies.Item(1).RangeBox
        Dim sx As Double=(bounds.MaxPoint.X-bounds.MinPoint.X)*10
        Dim sy As Double=(bounds.MaxPoint.Y-bounds.MinPoint.Y)*10
        Dim sz As Double=(bounds.MaxPoint.Z-bounds.MinPoint.Z)*10
        If sx>40.001 OrElse sy>40.001 OrElse sz>70.001 Then Throw New Exception("La envolvente supera 40x40x70 mm.")
        tx.End()
        tx=Nothing
        ThisApplication.ActiveView.Fit()
        MessageBox.Show("Maqueta editable creada: " & Math.Round(sx,2) & " x " & Math.Round(sy,2) & " x " & Math.Round(sz,2) & " mm." & vbCrLf & _
            "Guarda con Ctrl+S como SEDAC_Maqueta_Editable_V01.ipt." & vbCrLf & _
            "Edita bocetos u operaciones del arbol. No vuelvas a ejecutar esta regla en la pieza creada.","SEDAC")
    Catch ex As Exception
        If tx IsNot Nothing Then tx.Abort()
        MessageBox.Show("MAQUETA EDITABLE V01" & vbCrLf & "Etapa: " & stage & vbCrLf & ex.ToString(),"SEDAC - Error")
    End Try
End Sub

Function SketchXY(cd As Inventor.PartComponentDefinition,z As Double,label As String) As Inventor.PlanarSketch
    Dim plane As Inventor.WorkPlane=cd.WorkPlanes.Item(3)
    If Math.Abs(z)>0.000001 Then
        plane=cd.WorkPlanes.AddByPlaneAndOffset(plane,z/10)
        plane.Name="P_" & label
        plane.Visible=False
    End If
    Dim sk As Inventor.PlanarSketch=cd.Sketches.Add(plane)
    sk.Name="B_" & label
    Return sk
End Function

Sub ExtrudeZ(cd As Inventor.PartComponentDefinition,sk As Inventor.PlanarSketch,h As Double,cut As Boolean,label As String)
    Dim op As Inventor.PartFeatureOperationEnum=Inventor.PartFeatureOperationEnum.kJoinOperation
    If cut Then op=Inventor.PartFeatureOperationEnum.kCutOperation
    Dim ed As Inventor.ExtrudeDefinition=cd.Features.ExtrudeFeatures.CreateExtrudeDefinition(sk.Profiles.AddForSolid(),op)
    ed.SetDistanceExtent(h/10,Inventor.PartFeatureExtentDirectionEnum.kPositiveExtentDirection)
    cd.Features.ExtrudeFeatures.Add(ed).Name=label
    sk.Visible=False
End Sub

Sub ExtrudeY(cd As Inventor.PartComponentDefinition,sk As Inventor.PlanarSketch,h As Double,label As String)
    Dim normal As Inventor.Vector=ThisApplication.TransientGeometry.CreateVector(0,0,1)
    normal.TransformBy(sk.SketchToModelTransform)
    Dim direction As Inventor.PartFeatureExtentDirectionEnum=Inventor.PartFeatureExtentDirectionEnum.kPositiveExtentDirection
    If normal.Y<0 Then direction=Inventor.PartFeatureExtentDirectionEnum.kNegativeExtentDirection
    Dim ed As Inventor.ExtrudeDefinition=cd.Features.ExtrudeFeatures.CreateExtrudeDefinition(sk.Profiles.AddForSolid(),Inventor.PartFeatureOperationEnum.kCutOperation)
    ed.SetDistanceExtent(h/10,direction)
    cd.Features.ExtrudeFeatures.Add(ed).Name=label
    sk.Visible=False
End Sub

Sub Block(cd As Inventor.PartComponentDefinition,label As String,x As Double,y As Double,z As Double,w As Double,d As Double,h As Double,Optional cut As Boolean=False)
    Dim sk As Inventor.PlanarSketch=SketchXY(cd,z,label)
    Dim tg As Inventor.TransientGeometry=ThisApplication.TransientGeometry
    sk.SketchLines.AddAsTwoPointRectangle(tg.CreatePoint2d(x/10,y/10),tg.CreatePoint2d((x+w)/10,(y+d)/10))
    ExtrudeZ(cd,sk,h,cut,label)
End Sub

Sub Disk(cd As Inventor.PartComponentDefinition,label As String,x As Double,y As Double,z As Double,r As Double,h As Double,cut As Boolean)
    Dim sk As Inventor.PlanarSketch=SketchXY(cd,z,label)
    sk.SketchCircles.AddByCenterRadius(ThisApplication.TransientGeometry.CreatePoint2d(x/10,y/10),r/10)
    ExtrudeZ(cd,sk,h,cut,label)
End Sub

Sub CapsuleCut(cd As Inventor.PartComponentDefinition,label As String,x As Double,y As Double,z As Double,length As Double,width As Double,h As Double,vertical As Boolean)
    Dim a As Double=(length-width)/2
    If vertical Then
        Block(cd,label & "_Centro",x-width/2,y-a,z,width,2*a,h,True)
        Disk(cd,label & "_Ext1",x,y-a,z,width/2,h,True)
        Disk(cd,label & "_Ext2",x,y+a,z,width/2,h,True)
    Else
        Block(cd,label & "_Centro",x-a,y-width/2,z,2*a,width,h,True)
        Disk(cd,label & "_Ext1",x-a,y,z,width/2,h,True)
        Disk(cd,label & "_Ext2",x+a,y,z,width/2,h,True)
    End If
End Sub

Sub Hex(sk As Inventor.PlanarSketch,x As Double,y As Double,af As Double)
    Dim tg As Inventor.TransientGeometry=ThisApplication.TransientGeometry
    Dim p(5) As Inventor.SketchPoint
    Dim r As Double=af/Math.Sqrt(3)
    For i As Integer=0 To 5
        Dim angle As Double=i*Math.PI/3
        p(i)=sk.SketchPoints.Add(tg.CreatePoint2d((x+r*Math.Cos(angle))/10,(y+r*Math.Sin(angle))/10),False)
    Next
    For i As Integer=0 To 5
        sk.SketchLines.AddByTwoPoints(p(i),p((i+1) Mod 6))
    Next
End Sub
